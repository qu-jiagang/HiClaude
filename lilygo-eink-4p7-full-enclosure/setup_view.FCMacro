# FreeCAD GUI Macro: Apply colors and set up visibility for stepped enclosure model
# Run this AFTER opening lilygo_enclosure_v15_stepped.FCStd in FreeCAD GUI

doc = FreeCAD.ActiveDocument
if doc is None:
    FreeCAD.Console.PrintError("No active document. Open the FCStd file first.\n")
else:
    colors = {
        "outer_shell_block": (0.30, 0.50, 0.90),
        "main_body_cavity": (0.25, 0.45, 0.85),
        "main_body_with_cutouts": (0.20, 0.40, 0.80),
        "button_insert": (0.95, 0.60, 0.20),
        "rear_cover_plate": (0.30, 0.75, 0.30),
        "rear_cover_battery_door": (0.25, 0.70, 0.25),
        "rear_cover_with_lip": (0.22, 0.68, 0.22),
        "rear_cover_wire_channels": (0.20, 0.65, 0.20),
        "rear_cover_pcb_bosses": (0.18, 0.62, 0.18),
        "battery_door_panel": (0.75, 0.30, 0.75),
        "battery_door_with_plug": (0.72, 0.28, 0.72),
        "battery_door_with_retainers": (0.70, 0.25, 0.70),
        "battery_door_complete": (0.68, 0.22, 0.68),
        "validation_bridges": (0.80, 0.80, 0.80),
        "final_assembly": (0.60, 0.60, 0.65),
    }

    for obj in doc.Objects:
        label = obj.Label
        if label in colors:
            r, g, b = colors[label]
            try:
                vo = obj.ViewObject
                vo.ShapeColor = (r, g, b, 0.0)
                # Make intermediate steps semi-transparent
                if "final" not in label and "assembly" not in label:
                    vo.Transparency = 45
                else:
                    vo.Transparency = 8
                # Hide all intermediate steps by default
                if "final" not in label:
                    vo.Visibility = False
            except:
                pass

    FreeCAD.Gui.SendMsgToActiveView("ViewFit")
    FreeCAD.Console.PrintMessage("View setup complete. Toggle feature visibility in the tree.\n")
